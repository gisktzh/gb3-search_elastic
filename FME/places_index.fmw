FME workspace places_index.fmw

Parameters:
- elastic_group =
- elastic_host =
- elastic_password =
- elastic_user =
- geodb_host =
- geodb_name =
- geodb_param_group =
- geodb_password =
- geodb_port =
- geodb_user =
- indices_group =
- indices_new_postfix =
- indices_old_postfix =
- swissnames_group =
- swissnames_lin =
- swissnames_pkt =
- swissnames_ply =

Readers:
- POSTGIS_2: POSTGIS from $(geodb_name)
- CSV2_1: CSV2 from $(swissnames_ply)
- CSV2_2: CSV2 from $(swissnames_lin)
- CSV2_3: CSV2 from $(swissnames_pkt)

arv_basis_avzh_gemeinden_f (reader POSTGIS_2)
    attributes: geodb_oid serial, objectid int4, objid varchar(40), name varchar(32), bfsnr int2, bearbeitungsdatum varchar(12), davzh_name varchar(32), davzh_date varchar(12), davzh_model varchar(32)
    -> AttributeCreator
AttributeCreator
    ATTR_TABLE = SET_TO type = gemeinde
    -> FeatureWriter_2 [ARV_ADRESSEN_P]
CSV (reader CSV2_3)
    attributes: UUID varchar(39), OBJEKTART varchar(27), OBJEKTKLASSE_TLM varchar(17), HOEHE varchar(1), GEBAEUDENUTZUNG varchar(4), NAME_UUID varchar(39), NAME varchar(51), STATUS varchar(10), SPRACHCODE varchar(39), NAMEN_TYP varchar(15), NAMENGRUPPE_UUID varchar(39), E uint32, N uint32, Z int32
    -> AttributeRenamer_2
AttributeRenamer_2
    ATTR_TABLE:
      RENAME_SET_DEFAULT OBJEKTART > type
      RENAME_SET_DEFAULT NAME > name
    MISSING_INPUT_ATTRS = REMOVE
    -> FeatureWriter_2 [ARV_ADRESSEN_P]
CSV (reader CSV2_1)
    attributes: UUID varchar(39), OBJEKTART varchar(26), OBJEKTKLASSE_TLM varchar(18), EINWOHNERKATEGORIE varchar(4), NAME_UUID varchar(39), NAME varchar(143), STATUS varchar(10), SPRACHCODE varchar(39), NAMEN_TYP varchar(15), NAMENGRUPPE_UUID varchar(39), E uint32, N uint32, Z uint32, ISCED varchar(8)
    -> AttributeRenamer_3
AttributeRenamer_3
    ATTR_TABLE:
      RENAME_SET_DEFAULT OBJEKTART > type
      RENAME_SET_DEFAULT NAME > name
    MISSING_INPUT_ATTRS = REMOVE
    -> FeatureWriter_2 [ARV_ADRESSEN_P]
CSV (reader CSV2_2)
    attributes: UUID varchar(39), OBJEKTART varchar(26), OBJEKTKLASSE_TLM varchar(20), KUNSTBAUTE varchar(20), NAME_UUID varchar(39), NAME varchar(55), STATUS varchar(10), SPRACHCODE varchar(39), NAMEN_TYP varchar(15), NAMENGRUPPE_UUID varchar(39), E uint32, N uint32, Z int32
    -> AttributeRenamer_4
AttributeRenamer_4
    ATTR_TABLE:
      RENAME_SET_DEFAULT OBJEKTART > type
      RENAME_SET_DEFAULT NAME > name
    MISSING_INPUT_ATTRS = REMOVE
    -> FeatureWriter_2 [ARV_ADRESSEN_P]
Note: Write to ES
FeatureWriter_2
    DATASET = $(elastic_host)
    DATASET_ATTR = _dataset
    ELASTICSEARCH_CLUSTER_AUTHENTICATION_METHOD = BASIC_AUTH
    ELASTICSEARCH_CLUSTER_BASIC_AUTH_PASSWORD = $(elastic_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> HTTPCaller_4
Note: Add Alias
HTTPCaller_4
    AUTH_METHOD = Basic
    AUTH_PASSWORD = $(elastic_password)
    AUTH_USERNAME = $(elastic_user)
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(elastic_host)/_aliases
    TRANSFER_TIMEOUT_LENGTH = 90
    UPLOAD_BODY:
      {
        "actions": [
          {
            "add": {
              "index": "places-$(indices_new_postfix)",
              "alias": "fme-places"
            }
          }
        ]
      }
    UPLOAD_CONTENT_TYPE = JSON (application/json)
    UPLOAD_TYPE = Specify Upload Body
    USE_COOKIES = No
    VERIFY_SSL_CERTIFICATES = No
    -> HTTPCaller_5
Note: Remove old index from Alias
HTTPCaller_5
    AUTH_METHOD = Basic
    AUTH_PASSWORD = $(elastic_password)
    AUTH_USERNAME = $(elastic_user)
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(elastic_host)/_aliases
    TRANSFER_TIMEOUT_LENGTH = 90
    UPLOAD_BODY:
      {
        "actions": [
          {
            "remove": {
              "index": "places-$(indices_old_postfix)",
              "alias": "fme-places"
              }
          }
        ]
      }
    UPLOAD_CONTENT_TYPE = JSON (application/json)
    UPLOAD_TYPE = Specify Upload Body
    USE_COOKIES = No
    VERIFY_SSL_CERTIFICATES = No
    -> HTTPCaller_3
    <REJECTED> -> HTTPCaller_3
Note: Remove old Index
HTTPCaller_3
    AUTH_METHOD = Basic
    AUTH_PASSWORD = $(elastic_password)
    AUTH_USERNAME = $(elastic_user)
    CONNECTION_TIMEOUT_LENGTH = 60
    ERROR_ATTR = _error
    FOLLOW_REDIRECTS = FOLLOW_WITH_GET
    HTTP_METHOD = DELETE
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(elastic_host)/places-$(indices_old_postfix)
    TRANSFER_TIMEOUT_LENGTH = 90
    UPLOAD_CONTENT_TYPE = JSON (application/json)
    UPLOAD_TYPE = Specify Upload Body
    USE_COOKIES = No
    VERIFY_SSL_CERTIFICATES = No
