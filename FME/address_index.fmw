FME workspace address_index.fmw

Parameters:
- elastic_group =
- elastic_host =
- elastic_password =
- elastic_user =
- geodb_host =
- geodb_name =
- geodb_param_group =
- geodb_password =
- geodb_port =
- geodb_user =
- indices_group =
- indices_new_postfix =
- indices_old_postfix =

Readers:
- POSTGIS_1: POSTGIS from $(geodb_name)

arv_basis_arv_adressen_p (reader POSTGIS_1)
    attributes: geodb_oid serial, objectid int4, bfsnr int4, onrp int4, plz int4, zusatzziffern varchar(2), ortschaftsname varchar(40), kanton varchar(2), strassenname varchar(60), hausnummer varchar(12), geomy float8, geomx float8, status varchar(1), status_gp varchar(1), parz_nr varchar(12), gvz_nr varchar(12), gwr_egid int4, gwr_edid int4, gebaeudeart varchar(50), quelle varchar(12), search_vector text
    -> AttributeRenamer
AttributeRenamer
    ATTR_TABLE:
      RENAME_SET_DEFAULT strassenname > street
      RENAME_SET_DEFAULT ortschaftsname > town
      RENAME_SET_DEFAULT hausnummer > no
    MISSING_INPUT_ATTRS = REMOVE
    -> FeatureWriter [ARV_ADRESSEN_P]
Note: Write to ES
FeatureWriter
    DATASET = $(elastic_host)
    DATASET_ATTR = _dataset
    ELASTICSEARCH_CLUSTER_AUTHENTICATION_METHOD = BASIC_AUTH
    ELASTICSEARCH_CLUSTER_BASIC_AUTH_PASSWORD = $(elastic_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> HTTPCaller
Note: Add Alias
HTTPCaller
    AUTH_METHOD = Basic
    AUTH_PASSWORD = $(elastic_password)
    AUTH_USERNAME = $(elastic_user)
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(elastic_host)/_aliases
    TRANSFER_TIMEOUT_LENGTH = 90
    UPLOAD_BODY:
      {
        "actions": [
          {
            "add": {
              "index": "addresses-$(indices_new_postfix)",
              "alias": "fme-addresses"
            }
          }
        ]
      }
    UPLOAD_CONTENT_TYPE = JSON (application/json)
    UPLOAD_TYPE = Specify Upload Body
    USE_COOKIES = No
    VERIFY_SSL_CERTIFICATES = No
    -> HTTPCaller_2
Note: Remove old index from Alias
HTTPCaller_2
    AUTH_METHOD = Basic
    AUTH_PASSWORD = $(elastic_password)
    AUTH_USERNAME = $(elastic_user)
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(elastic_host)/_aliases
    TRANSFER_TIMEOUT_LENGTH = 90
    UPLOAD_BODY:
      {
        "actions": [
          {
            "remove": {
              "index": "addresses-$(indices_old_postfix)",
              "alias": "fme-addresses"
              }
          }
        ]
      }
    UPLOAD_CONTENT_TYPE = JSON (application/json)
    UPLOAD_TYPE = Specify Upload Body
    USE_COOKIES = No
    VERIFY_SSL_CERTIFICATES = No
    -> HTTPCaller_3
    <REJECTED> -> HTTPCaller_3
Note: Remove old Index
HTTPCaller_3
    AUTH_METHOD = Basic
    AUTH_PASSWORD = $(elastic_password)
    AUTH_USERNAME = $(elastic_user)
    CONNECTION_TIMEOUT_LENGTH = 60
    ERROR_ATTR = _error
    FOLLOW_REDIRECTS = FOLLOW_WITH_GET
    HTTP_METHOD = DELETE
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(elastic_host)/addresses-$(indices_old_postfix)
    TRANSFER_TIMEOUT_LENGTH = 90
    UPLOAD_CONTENT_TYPE = JSON (application/json)
    UPLOAD_TYPE = Specify Upload Body
    USE_COOKIES = No
    VERIFY_SSL_CERTIFICATES = No
