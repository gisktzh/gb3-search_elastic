FME workspace address_index (backup).fmw

Parameters:
- SourceDataset_FILEGDB =
- datestamp =
- datestamp_old =

Readers:
- FILEGDB_1: FILEGDB from $(SourceDataset_FILEGDB) in EPSG:2056

FLGEW_SUCHE_L (reader FILEGDB_1)
    attributes: OBJECTID objectid, GEWAESSERNUMMER double, BFS smallint, GEMEINDENAME text(60), GEMEINDEGEWAESSERNUMMER text(10), GEWAESSERNAME text(100), LYR text(20), SHAPE_Length double
STEHGEW_SUCHE_F (reader FILEGDB_1)
    attributes: OBJECTID objectid, GEWAESSERNUMMER double, BFS smallint, GEMEINDENAME text(60), GEWAESSERNAME text(100), LYR text(20), SHAPE_Length double, SHAPE_Area double
STR_KM_L_M (reader FILEGDB_1)
    attributes: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
ARV_ADRESSEN_P (reader FILEGDB_1)
    attributes: OBJECTID objectid, BFSNR int, ONRP int, PLZ int, ZUSATZZIFFERN text(2), ORTSCHAFTSNAME text(40), KANTON text(2), STRASSENNAME text(60), HAUSNUMMER text(12), GEOMY double, GEOMX double, STATUS text(1), STATUS_GP text(1), PARZ_NR text(12), GVZ_NR text(12), GWR_EGID int, GWR_EDID int, GEBAEUDEART text(50), QUELLE text(12)
    -> AttributeRenamer
AttributeRenamer
    ATTR_TABLE = RENAME_SET_DEFAULT STRASSENNAME > street
    MISSING_INPUT_ATTRS = REMOVE
    -> FeatureWriter [ARV_ADRESSEN_P]
Note: Write to ES
FeatureWriter
    DATASET = http://localhost:9200
    DATASET_ATTR = _dataset
    ELASTICSEARCH_CLUSTER_AUTHENTICATION_METHOD = BASIC_AUTH
    ELASTICSEARCH_CLUSTER_BASIC_AUTH_PASSWORD =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
    ELASTICSEARCH_CLUSTER_BASIC_AUTH_USERNAME = elastic
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> HTTPCaller
Note: Add Alias
HTTPCaller
    AUTH_METHOD = Basic
    AUTH_PASSWORD =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
    AUTH_USERNAME = elastic
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = http://localhost:9200/_aliases
    TRANSFER_TIMEOUT_LENGTH = 90
    UPLOAD_BODY:
      {
        "actions": [
          {
            "add": {
              "index": "addresses-$(datestamp)",
              "alias": "fme-addresses"
            }
          }
        ]
      }
    UPLOAD_CONTENT_TYPE = JSON (application/json)
    UPLOAD_TYPE = Specify Upload Body
    USE_COOKIES = No
    VERIFY_SSL_CERTIFICATES = No
    -> HTTPCaller_2
Note: Remove Alias
HTTPCaller_2
    AUTH_METHOD = Basic
    AUTH_PASSWORD =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
    AUTH_USERNAME = elastic
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = http://localhost:9200/_aliases
    TRANSFER_TIMEOUT_LENGTH = 90
    UPLOAD_BODY:
      {
        "actions": [
          {
            "remove": {
              "index": "addresses-$(datestamp_old)",
              "alias": "fme-addresses"
              }
          }
        ]
      }
    UPLOAD_CONTENT_TYPE = JSON (application/json)
    UPLOAD_TYPE = Specify Upload Body
    USE_COOKIES = No
    VERIFY_SSL_CERTIFICATES = No
