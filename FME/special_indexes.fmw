FME workspace special_indexes.fmw

Parameters:
- elastic_group =
- elastic_host =
- elastic_password =
- elastic_user =
- geodb_host =
- geodb_name =
- geodb_param_group =
- geodb_password =
- geodb_port =
- geodb_user =
- indices_group =
- indices_new_postfix =
- indices_old_postfix =

Readers:
- POSTGIS_2: POSTGIS from $(geodb_name)

giszhpub_wb_gewaesserbezeichnung_suche_geom_v (reader POSTGIS_2)
    attributes: geodb_oid int4, gemeindegewaessernummer varchar(80), gemeindename varchar(60), gewaessername varchar(100), gewaessernummer float8, bfs int2, lyr varchar(20)
    -> FeatureWriter [ARV_ADRESSEN_P]
Note: Write to ES
FeatureWriter
    DATASET = $(elastic_host)
    DATASET_ATTR = _dataset
    ELASTICSEARCH_CLUSTER_AUTHENTICATION_METHOD = BASIC_AUTH
    ELASTICSEARCH_CLUSTER_BASIC_AUTH_PASSWORD = $(elastic_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> FeatureHolder
tba_si_verkehrstechnik_bsa_p (reader POSTGIS_2)
    attributes: geodb_oid serial,PrimaryKey, id_bsa float8, guid uuid, typ varchar(10), typ_id int4, typ_bez varchar(100), status varchar(10), status_id int4, status_bez varchar(100), objektangaben varchar(255), anlagenummer varchar(255), bezeichnung varchar(255)
    -> FeatureWriter_13 [ARV_ADRESSEN_P]
Note: Write to ES
FeatureWriter_13
    DATASET = $(elastic_host)
    DATASET_ATTR = _dataset
    ELASTICSEARCH_CLUSTER_AUTHENTICATION_METHOD = BASIC_AUTH
    ELASTICSEARCH_CLUSTER_BASIC_AUTH_PASSWORD = $(elastic_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> FeatureHolder
tba_si_velo_mb_sk_netz_l_m (reader POSTGIS_2)
    attributes: geodb_oid serial,PrimaryKey, rte_plus varchar(255), rte_minus varchar(255), rw_key varchar(255), richtplantyp varchar(255), rw_key_nr varchar(255), kmmin float8, kmmax float8, laenge_m float8, numofpart float8, verbindungsname varchar(300), pdf_pfad varchar(500), zweck varchar(255), routentyp varchar(255), fahrrichtungstyp varchar(50), planungstyp varchar(50)
    -> FeatureWriter_12 [ARV_ADRESSEN_P]
Note: Write to ES
FeatureWriter_12
    DATASET = $(elastic_host)
    DATASET_ATTR = _dataset
    ELASTICSEARCH_CLUSTER_AUTHENTICATION_METHOD = BASIC_AUTH
    ELASTICSEARCH_CLUSTER_BASIC_AUTH_PASSWORD = $(elastic_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> FeatureHolder
tba_si_str_beleuchtung_p (reader POSTGIS_2)
    attributes: geodb_oid serial,PrimaryKey, objectid int4, achsnummer varchar(20), ausgeschal varchar(1), bauart int4, baujahr float8, beleuchtun int4, nummer varchar(50), startdista float8, dat_logo varchar(255), ausgeschaltet_txt varchar(255), beleuchtungstyp_txt varchar(255), bauart_txt varchar(255), gemeinden varchar(100), strassenname varchar(100), lichtpunkthoehe float8, code float8
    -> FeatureWriter_10 [ARV_ADRESSEN_P]
Note: Write to ES
FeatureWriter_10
    DATASET = $(elastic_host)
    DATASET_ATTR = _dataset
    ELASTICSEARCH_CLUSTER_AUTHENTICATION_METHOD = BASIC_AUTH
    ELASTICSEARCH_CLUSTER_BASIC_AUTH_PASSWORD = $(elastic_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> FeatureHolder
tba_si_nse_schaechte_p (reader POSTGIS_2)
    attributes: geodb_oid serial,PrimaryKey, eigentum varchar(80), unterhalt varchar(80), funktion varchar(80), lagegena varchar(80), schacht_nr varchar(20), gemknr varchar(20), unt_funkt varchar(160), jahr varchar(50), point_x float8, point_y float8
    -> FeatureWriter_9 [ARV_ADRESSEN_P]
Note: Write to ES
FeatureWriter_9
    DATASET = $(elastic_host)
    DATASET_ATTR = _dataset
    ELASTICSEARCH_CLUSTER_AUTHENTICATION_METHOD = BASIC_AUTH
    ELASTICSEARCH_CLUSTER_BASIC_AUTH_PASSWORD = $(elastic_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> FeatureHolder
giszhpub_wb_wasserrechte_suche_p_v (reader POSTGIS_2)
    attributes: geodb_oid int4, wasserrechts_nr varchar(30), laufnummer int2, rechtsstatus_code int2, rechtsstatus_txt varchar(80), zustand_code int2, zustand_txt varchar(80), zweck_code varchar(30), zweck_txt varchar(80), knotentyp_code int4, knotentyp_txt varchar(80), gewaessername varchar(100), gewaessernummer float8, vfg_nr varchar(30), vfg_datum timestamp, vfg_link varchar(250)
    -> FeatureWriter_8 [ARV_ADRESSEN_P]
Note: Write to ES
FeatureWriter_8
    DATASET = $(elastic_host)
    DATASET_ATTR = _dataset
    ELASTICSEARCH_CLUSTER_AUTHENTICATION_METHOD = BASIC_AUTH
    ELASTICSEARCH_CLUSTER_BASIC_AUTH_PASSWORD = $(elastic_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> FeatureHolder
giszhpub_vs_verkehrsmessstellen_p (reader POSTGIS_2)
    attributes: geodb_oid serial,PrimaryKey, objectid int4, messst_nr int2,BTREE, x_koordinate float8, y_koordinate float8, km float8, kt_rte_key float4, strassenname varchar(50), messst_dateiname char(20), dtv int4, dtv_bezugsjahr int2, messst_typ_code int2, messst_typ char(15), nt int4, nn int4, vm int4, vmt int4, vmn int4, v85 int4, v85t int4, v85n int4, dsv float8, nt2 float8, nn2 float8, dlv float4, dtvjahr_lv int4, betreiber varchar(255)
    -> FeatureWriter_7 [ARV_ADRESSEN_P]
Note: Write to ES
FeatureWriter_7
    DATASET = $(elastic_host)
    DATASET_ATTR = _dataset
    ELASTICSEARCH_CLUSTER_AUTHENTICATION_METHOD = BASIC_AUTH
    ELASTICSEARCH_CLUSTER_BASIC_AUTH_PASSWORD = $(elastic_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> FeatureHolder
giszhpub_gs_gwr_suche_p (reader POSTGIS_2)
    attributes: geodb_oid serial,PrimaryKey, objectid int4, gwr_aqua varchar(255),BTREE, gwr varchar(255), y_koord float8, x_koord float8, gwr_id char(50)
    -> FeatureWriter_6 [ARV_ADRESSEN_P]
Note: Write to ES
FeatureWriter_6
    DATASET = $(elastic_host)
    DATASET_ATTR = _dataset
    ELASTICSEARCH_CLUSTER_AUTHENTICATION_METHOD = BASIC_AUTH
    ELASTICSEARCH_CLUSTER_BASIC_AUTH_PASSWORD = $(elastic_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> FeatureHolder
awel_wb_sbk_geoboje_singlepart_p (reader POSTGIS_2)
    attributes: geodb_oid serial,PrimaryKey, beschreibung varchar(200), objektnr int4, symbcode varchar(4), zhnr varchar(50)
    -> FeatureWriter_5 [ARV_ADRESSEN_P]
Note: Write to ES
FeatureWriter_5
    DATASET = $(elastic_host)
    DATASET_ATTR = _dataset
    ELASTICSEARCH_CLUSTER_AUTHENTICATION_METHOD = BASIC_AUTH
    ELASTICSEARCH_CLUSTER_BASIC_AUTH_PASSWORD = $(elastic_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> FeatureHolder
arv_basis_avzh_gvznummersuche_f_v (reader POSTGIS_2)
    attributes: geodb_oid int4, geodb_oid_orig int4, geomsource text, gvznummer varchar(12), bfsnr int2
    -> FeatureWriter_4 [ARV_ADRESSEN_P]
Note: Write to ES
FeatureWriter_4
    DATASET = $(elastic_host)
    DATASET_ATTR = _dataset
    ELASTICSEARCH_CLUSTER_AUTHENTICATION_METHOD = BASIC_AUTH
    ELASTICSEARCH_CLUSTER_BASIC_AUTH_PASSWORD = $(elastic_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> FeatureHolder
aln_lw_agricola_bienenstaende_p_v (reader POSTGIS_2)
    attributes: geodb_oid int4, stand_nr varchar(14), aktiv varchar(4), stand_bezirk varchar(50), stand_bfsnr varchar(4), stand_name varchar(50), stand_plz varchar(4), gemeindename varchar(50), lky int4, lkx int4, voelker int4, imker_id varchar(20), adress_nr int4, betriebs_nr int4, nachname varchar(80), vorname varchar(80), adresse varchar(35), plz varchar(4), wohnort varchar(30), telefon_nr varchar(16), mobile_nr varchar(16), email varchar(80), beruf varchar(50), jahrgang varchar(4)
    -> FeatureWriter_3 [ARV_ADRESSEN_P]
Note: Write to ES
FeatureWriter_3
    DATASET = $(elastic_host)
    DATASET_ATTR = _dataset
    ELASTICSEARCH_CLUSTER_AUTHENTICATION_METHOD = BASIC_AUTH
    ELASTICSEARCH_CLUSTER_BASIC_AUTH_PASSWORD = $(geodb_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> FeatureHolder
tba_si_str_km_l_m (reader POSTGIS_2)
    attributes: geodb_oid serial,PrimaryKey, objectid int4, kantstreet int4, id int4, kt_rte_key float8, minkm float8, maxkm float8, jahr varchar(50), route_schluessel int4, strassenname varchar(30), arclength float8, measurelength float8, strassenname_search varchar(150), strassenname_kat int4, strassenname_kat_string varchar(50)
    -> FeatureWriter_11 [ARV_ADRESSEN_P]
Note: Write to ES
FeatureWriter_11
    DATASET = $(elastic_host)
    DATASET_ATTR = _dataset
    ELASTICSEARCH_CLUSTER_AUTHENTICATION_METHOD = BASIC_AUTH
    ELASTICSEARCH_CLUSTER_BASIC_AUTH_PASSWORD = $(elastic_password)
    ELASTICSEARCH_CLUSTER_BASIC_AUTH_USERNAME = $(elastic_user)
    ELASTICSEARCH_CLUSTER_COMPLY_TO_EXISTING_SCHEMA = NO
    ELASTICSEARCH_CLUSTER_USE_AUTHENTICATION = YES
    ELASTICSEARCH_CLUSTER_USE_BULK_INSERT = Yes
    ELASTICSEARCH_CLUSTER_WRITE_NULLS = YES
    FEATURE_TYPE_LIST_ATTR = _feature_types
    FORMAT = ELASTICSEARCH_CLUSTER
    TOTAL_FEATURES_WRITTEN_ATTR = _total_features_written
    SUMMARY -> FeatureHolder
Note: Wait for all features
FeatureHolder
    -> Sampler
Note: Pick only one, to run clean up only once
Sampler
    RATE = 1
    SAMPLE_MODE = No
    SAMPLE_TYPE_LONG = First N Features
    SAMPLED -> HTTPCaller
Note: Add Aliases
HTTPCaller
    AUTH_METHOD = Basic
    AUTH_PASSWORD = $(elastic_password)
    AUTH_USERNAME = $(elastic_user)
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(elastic_host)/_aliases
    TRANSFER_TIMEOUT_LENGTH = 90
    UPLOAD_BODY:
      {
        "actions": [
          {
            "add": {
              "index": "gewaesserangaben-$(indices_new_postfix)",
              "alias": "gewaesserangaben"
            }
          },
          {
            "add": {
              "index": "verkehrsmessstellen-$(indices_new_postfix)",
              "alias": "verkehrsmessstellen"
            }
          },
          {
            "add": {
              "index": "verkehrstechnik-$(indices_new_postfix)",
              "alias": "verkehrstechnik"
            }
          },
          {
            "add": {
              "index": "beleuchtung-$(indices_new_postfix)",
              "alias": "beleuchtung"
            }
          },
          {
            "add": {
              "index": "schacht-$(indices_new_postfix)",
              "alias": "schacht"
            }
          },
          {
            "add": {
              "index": "wasserrechtwww-$(indices_new_postfix)",
              "alias": "wasserrechtwww"
            }
          },
          {
            "add": {
              "index": "fassung-$(indices_new_postfix)",
              "alias": "fassung"
            }
          },
          {
            "add": {
              "index": "gvz-$(indices_new_postfix)",
              "alias": "gvz"
            }
          },
          {
            "add": {
              "index": "bienenstaende-$(indices_new_postfix)",
              "alias": "bienenstaende"
            }
          },
          {
            "add": {
              "index": "veloverbindungen-$(indices_new_postfix)",
              "alias": "veloverbindungen"
            }
          },
          {
            "add": {
              "index": "strkm-$(indices_new_postfix)",
              "alias": "strkm"
            }
          },
          {
            "add": {
              "index": "boje-$(indices_new_postfix)",
              "alias": "boje"
            }
          }
        ]
      }
    UPLOAD_CONTENT_TYPE = JSON (application/json)
    UPLOAD_TYPE = Specify Upload Body
    USE_COOKIES = No
    VERIFY_SSL_CERTIFICATES = No
    -> HTTPCaller_2
Note: Remove old indices from Alias
HTTPCaller_2
    AUTH_METHOD = Basic
    AUTH_PASSWORD = $(elastic_password)
    AUTH_USERNAME = $(elastic_user)
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(elastic_host)/_aliases
    TRANSFER_TIMEOUT_LENGTH = 90
    UPLOAD_BODY:
      {
        "actions": [
          {
            "remove": {
              "index": "gewaesserangaben-$(indices_old_postfix)",
              "alias": "gewaesserangaben"
            }
          },
          {
            "remove": {
              "index": "verkehrsmessstellen-$(indices_old_postfix)",
              "alias": "verkehrsmessstellen"
            }
          },
          {
            "remove": {
              "index": "verkehrstechnik-$(indices_old_postfix)",
              "alias": "verkehrstechnik"
            }
          },
          {
            "remove": {
              "index": "beleuchtung-$(indices_old_postfix)",
              "alias": "beleuchtung"
            }
          },
          {
            "remove": {
              "index": "schacht-$(indices_old_postfix)",
              "alias": "schacht"
            }
          },
          {
            "remove": {
              "index": "wasserrechtwww-$(indices_old_postfix)",
              "alias": "wasserrechtwww"
            }
          },
          {
            "remove": {
              "index": "fassung-$(indices_old_postfix)",
              "alias": "fassung"
            }
          },
          {
            "remove": {
              "index": "gvz-$(indices_old_postfix)",
              "alias": "gvz"
            }
          },
          {
            "remove": {
              "index": "bienenstaende-$(indices_old_postfix)",
              "alias": "bienenstaende"
            }
          },
          {
            "remove": {
              "index": "veloverbindungen-$(indices_old_postfix)",
              "alias": "veloverbindungen"
            }
          },
          {
            "remove": {
              "index": "strkm-$(indices_old_postfix)",
              "alias": "strkm"
            }
          },
          {
            "remove": {
              "index": "boje-$(indices_old_postfix)",
              "alias": "boje"
            }
          }
        ]
      }
    UPLOAD_CONTENT_TYPE = JSON (application/json)
    UPLOAD_TYPE = Specify Upload Body
    USE_COOKIES = No
    VERIFY_SSL_CERTIFICATES = No
    -> HTTPCaller_4
    <REJECTED> -> HTTPCaller_4
Note: Remove old indices; comma-separated list
HTTPCaller_4
    AUTH_METHOD = Basic
    AUTH_PASSWORD = $(elastic_password)
    AUTH_USERNAME = $(elastic_user)
    CONNECTION_TIMEOUT_LENGTH = 60
    ERROR_ATTR = _error
    FOLLOW_REDIRECTS = FOLLOW_WITH_GET
    HTTP_METHOD = DELETE
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(elastic_host)/gewaesserangaben-$(indices_old_postfix),verkehrsmessstellen-$(indices_old_postfix),verkehrstechnik-$(indices_old_postfix),beleuchtung-$(indices_old_postfix),schacht-$(indices_old_postfix),wasserrechtwww-$(indices_old_postfix),fassung-$(indices_old_postfix),gvz-$(indices_old_postfix),bienenstaende-$(indices_old_postfix),veloverbindungen-$(indices_old_postfix),strkm-$(indices_old_postfix),boje-$(indices_old_postfix)
    TRANSFER_TIMEOUT_LENGTH = 90
    UPLOAD_CONTENT_TYPE = JSON (application/json)
    UPLOAD_TYPE = Specify Upload Body
    USE_COOKIES = No
    VERIFY_SSL_CERTIFICATES = No
